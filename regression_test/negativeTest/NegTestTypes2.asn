--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Szabo, Bence Janos
--
--/////////////////////////////////////////////////////////////////////////////
NegTestTypes2
DEFINITIONS
AUTOMATIC TAGS
::= BEGIN
IMPORTS ;


ExtensionRecord ::= SEQUENCE {
  me INTEGER DEFAULT 5,
  ...,
  f0 INTEGER DEFAULT 5,
  f1 INTEGER DEFAULT 5,
  f2 INTEGER OPTIONAL
}

END
