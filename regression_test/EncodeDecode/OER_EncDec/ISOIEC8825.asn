ISOIEC8825 DEFINITIONS ::=

BEGIN

  IMPORTS;

  Date ::= [APPLICATION 3] IMPLICIT VisibleString -- YYYYMMDD
  EmployeeNumber ::= [APPLICATION 2] IMPLICIT INTEGER
  Name ::= [APPLICATION 1] IMPLICIT SEQUENCE   {
	givenName VisibleString,
	initial VisibleString,
	familyName VisibleString }
  ChildInformation ::= SET {
	name Name,
	dateOfBirth [0] Date}
  Record ::= [APPLICATION 0] IMPLICIT SET {
	name Name,
	title [0] VisibleString,
	number EmployeeNumber,
	dateOfHire [1] Date,
	nameOfSpouse [2] Name,
	children [3] IMPLICIT SEQUENCE OF ChildInformation DEFAULT {} }
END
