--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Baranyi, Botond
--
--/////////////////////////////////////////////////////////////////////////////
JsonBasicASN1Types DEFINITIONS

  AUTOMATIC TAGS ::=

BEGIN

IMPORTS ;

Asn1-bs ::= BIT STRING
Asn1-bool ::= BOOLEAN
Asn1-bmpstr ::= BMPString
Asn1-Number ::= CHOICE {
  decimal INTEGER,
  binary BIT STRING,
  hexadecimal OCTET STRING
}

--T-REC X.680-200811, Chapter 41
--Definition of Restricted character string types
Asn1-genstr ::= GeneralString
Asn1-graphstr ::= GraphicString
Asn1-ia5str ::= IA5String
Asn1-ISO646String ::= ISO646String
Asn1-numstr ::= NumericString
Asn1-pstr ::= PrintableString
Asn1-teletexstr ::= TeletexString --T61String
Asn1-t61str ::= T61String  
Asn1-univstr ::= UniversalString
Asn1-utf8str ::= UTF8String
Asn1-videotexstr ::= VideotexString
Asn1-visiblestr ::= VisibleString


Asn1-i ::= INTEGER
Asn1-f ::= REAL
Asn1-null ::= NULL

Asn1-oid ::= OBJECT IDENTIFIER
Asn1-os ::= OCTET STRING

Asn1-seqofI ::= SEQUENCE OF INTEGER
Asn1-setofI ::= SET OF INTEGER

END
