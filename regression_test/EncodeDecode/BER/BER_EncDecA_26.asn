--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Kristof, Szabados
--
--/////////////////////////////////////////////////////////////////////////////
BER-EncDecA-26


DEFINITIONS
AUTOMATIC TAGS
::=
BEGIN
BERPDU ::= SET
      {
	b  [5] BOOLEAN OPTIONAL,
	c   INTEGER OPTIONAL
      }
END
