--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Kristof, Szabados
--
--/////////////////////////////////////////////////////////////////////////////
BER-EncDecA-32


DEFINITIONS

AUTOMATIC TAGS

::=

BEGIN


MySeq ::= SET
      {y OCTET STRING,
       x  INTEGER OPTIONAL
       }



BERPDU ::= SET
      {   
	b   [0]  BOOLEAN OPTIONAL,
	c   BIT STRING OPTIONAL,
	COMPONENTS OF MySeq
      }


END
