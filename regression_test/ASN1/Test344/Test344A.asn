--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Raduly, Csaba
--   Szabados, Kristof
--
--/////////////////////////////////////////////////////////////////////////////
Test344A
DEFINITIONS

AUTOMATIC TAGS

::=

BEGIN

MyObjectIdentifierType1 ::= OBJECT IDENTIFIER

myObjectIdentifierValue1 MyObjectIdentifierType1 ::= {abrax(0) brabax(3) califax(7)}

END
