--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--
--/////////////////////////////////////////////////////////////////////////////
Test10

DEFINITIONS

AUTOMATIC TAGS

::=

BEGIN
MySequenceType1 ::= SEQUENCE {
  			     field1 INTEGER,
			     field2 BOOLEAN,
			     field3 NULL,
			     field4 OCTET STRING,
			     field5 BIT STRING,
			     field6 ENUMERATED {a,b,c},
			     field7 REAL
			    }

mySequenceValue1 MySequenceType1 ::=  {
  			     field1 555,                            -- INTEGER,
			     field2 TRUE,                            -- BOOLEAN,
			     field3 NULL,
	-- missing field4
			     field5 '01010'B,                        -- BIT STRING,
			     field6  a,                             --ENUMERATED {a,b,c},
			     field7  {mantissa 10,base 2, exponent 2}        --REAL
			    }

END
