--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Koppany, Csaba
--   Kulcsar, Endre
--   Szabados, Kristof
--
--/////////////////////////////////////////////////////////////////////////////
Test1

DEFINITIONS

AUTOMATIC TAGS

::=

BEGIN

--Test Case 1
/*

Csaba wanted these comments to be taken out:

PLUS-INFINITY and MINUS-INFINITY not supported and commented out,

 ...,... not supp in beginning of SET and SEQUENCE if other fields follow,
 MySetType5, MySequenceType8,
 ...[[]]... not supported in CHOICE (MyChoiceType4),

 MyEnumeratedType1 commented out because ExceptionSpec not supported
 in enumerated

MySetType5 commented out because of problems with COMPONENTS OF

SELECTION TYPES not supported and commented out

UNIVERSAL 0 commented out

EXTERNAL type not implemented  and commented out

EMBEDDED PDV type is not implemented and commented out

only cstring format of IA5String is supported, the rest is commented out
the other character string types  are not yet implemented

UNRESTRICTED CHARACTER TYPE not supported and commented out

GeneralizedTime not supported and commented out

UTCTime not supported and commented out

*/

-- 11.6.4 Comments *********************************************************

-- simple comment

  -- simple comment2 --  myBooleanValuexxx BOOLEAN ::= TRUE  --simple comment3--

  -- /* simple comment 4*/ --
  -- /* simple comment 5*/

/*
Comment start
end of comment */

/* Comment start
/* Comment continues
*/ not end of comment
end of comment */

/*
`1234567890-=~!@#$%^&*()_+
qwertyuiop[]\QWERTYUIOP{}|
asdfghjkl;'ASDFGHJKL:"
zxcvbnm,./ZXCVBNM<>?
-- still part of comment1 -- abcd
-- still part of comment

íöüóõúûéá
*/

--17  BOOLEAN *********************************************************

myBooleanValue1 BOOLEAN ::= TRUE

myBooleanValue2 BOOLEAN ::= FALSE

MyBooleanType1 ::= BOOLEAN

myBooleanValue3 MyBooleanType1 ::= TRUE

myBooleanValue4 MyBooleanType1 ::= FALSE

myBooleanValue5 MyBooleanType1 ::= myBooleanValue1

abcdefghijklmnopqrstuvwxyzABCDEFGHIJKLMNOPQRSTUVWXYZ-0123456789 BOOLEAN ::= myBooleanValue1

ABCDEFGHIJKLMNOPQRSTUVWXYZabcdefghijklmnopqrstuvwxyz-0123456789 ::= BOOLEAN

--18 INTEGER **********************************************************

myIntegerValue1 INTEGER ::= 19700313

myIntegerValue2 INTEGER ::= 0

myIntegerValue3 INTEGER ::= -191919

MyIntegerType1 ::= INTEGER

myIntegerValue4 MyIntegerType1 ::= 55555

myIntegerValue5 MyIntegerType1 ::= myIntegerValue1

MyIntegerType2 ::= INTEGER { firstvalue(-100), secondvalue(0), othervalue(100) } -- named numbers

MyIntegerType3 ::= INTEGER { firstvalue(myIntegerValue1), secondvalue(myIntegerValue2),
			 othervalue(myIntegerValue3) } -- named numbers (defined value)

myIntegerValue6 MyIntegerType2 ::= firstvalue

myIntegerValue7 MyIntegerType2 ::= 99

a INTEGER ::=1
T1 ::= INTEGER {a(2)}
T2 ::= INTEGER {a(3), b(a)}
c T2 ::= b
d T2 ::= a

MyIntegerType4 ::= INTEGER (0..15, ..., 0..31)

-- 19 ENUMERATED *******************************************************
-- valid

MyEnumeratedType0 ::= ENUMERATED {a,b,c}

-- MyEnumeratedType1 ::= ENUMERATED {a,b,...!,c}

MyEnumeratedType2 ::= ENUMERATED {a(0) ,b, ..., c}

MyEnumeratedType3 ::= ENUMERATED {a(1) ,b,..., c}

MyEnumeratedType4 ::= ENUMERATED {a(1),b,..., c(2)}

MyEnumeratedType5 ::= ENUMERATED {a(0),b(1),..., c(2)}

MyEnumeratedType6 ::= ENUMERATED {a(1),b(0),..., c(2)}

MyEnumeratedType7 ::= ENUMERATED {a(2),b(1),..., c(0)}

MyEnumeratedType8 ::= ENUMERATED {a(0),b(2),..., c(1)}

MyEnumeratedType9 ::= ENUMERATED {a(0),b(2),..., c }

MyEnumeratedType10 ::= ENUMERATED {a,b,...,c,d(3)}

MyEnumeratedType11 ::= ENUMERATED {a(1),b(0),...,c,d(3)}

MyEnumeratedType12 ::= ENUMERATED {a,b,...,c(2),d}

MyEnumeratedType13 ::= ENUMERATED {a,b,...,c(2),d(3)}

MyEnumeratedType14 ::= ENUMERATED {a(2),b(3),...,c,d}

MyEnumeratedType15 ::= ENUMERATED {a(2),b(3),...,c(0),d(1)}

MyEnumeratedType16 ::= ENUMERATED {first(1), second(9999),third,fourth(2), ..., fifth(3),
	 abcdefghijklmnopqrstuvwxyzABCDEFGHIJKLMNOPQRSTUVWXYZ-0123456789, last(5)}

myEnumearetedValue1  MyEnumeratedType16  ::= first

myEnumearetedValue2  MyEnumeratedType16  ::= last

-- 20 REAL *******************************************************

MyRealType1 ::= REAL

MyRealType2 ::= REAL (WITH COMPONENTS {..., base(10)})

MyRealType3 ::= REAL (WITH COMPONENTS {..., base(2)})

myRealValue1 REAL ::= {mantissa 314159,base 10, exponent -10}

myRealValue2 MyRealType2 ::= {mantissa 314159,base 10, exponent -10}

myRealValue3 MyRealType3 ::= {mantissa 1234,base 2, exponent 1}

myRealValue4 REAL::= PLUS-INFINITY

myRealValue5 REAL ::= MINUS-INFINITY

-- 21 BIT STRING *******************************************************

MyBitstringType1 ::= BIT STRING

myBitstringValue1 MyBitstringType1 ::= '0101010101010101'B

myBitstringValue2 MyBitstringType1 ::= '01234567890ABCDEF'H

myBitstringValue3 BIT STRING ::= '010101010101010'B

myBitstringValue4 BIT STRING ::= '01234567890ABCDEF'H

MyBitstringType2 ::= BIT STRING{ first(0), second (1), last-in-first-octet(7) }

myBitstringValue5 MyBitstringType2 ::= {first, last-in-first-octet }

myBitstringValue6 MyBitstringType2 ::= {}

myBitstringValue7 MyBitstringType2 ::= '01234567890ABCDEF'H

myBitstringValue8 BIT STRING ::= '00 01  11'B --Section 11.10 occurences of white space...have no significance

-- 22 OCTET STRING  *******************************************************

MyOctetStringType1 ::= OCTET STRING

myOctetstringValue1  OCTET STRING ::= '1234567890ABCDEF'H

myOctetstringValue2  OCTET STRING ::= '1234567890ABCDEF1'H

myOctetstringValue3  OCTET STRING ::= '01010101'B

myOctetstringValue4  OCTET STRING ::= '00011'B

myOctetstringValue5  OCTET STRING ::= '1 2 34567  890ABC DEF 'H

--23 NULL *******************************************************

MyNullType1 ::= NULL

myNullValue1 NULL ::= NULL

myNullValue2 MyNullType1 ::= NULL

-- 24 SEQUENCE *******************************************************

MySequenceType0 ::= SEQUENCE {}

MySequenceType1 ::= SEQUENCE {
  			     field1 INTEGER,
			     field2 BOOLEAN,
			     field3 NULL,
			     field4 OCTET STRING,
			     field5 BIT STRING,
			     field6 ENUMERATED {a,b,c},
			     field7 REAL
			    }

MySequenceType2 ::= SEQUENCE  {
				 field1	 MyIntegerType1,
				 field2  MyBooleanType1,
				 field3  MyNullType1,
				 field4  MyOctetStringType1,
				 field5  MyBitstringType1,
				 field6  MyEnumeratedType2,
				 field7  MyRealType1
			   }

MySequenceType3 ::= SEQUENCE  {
				 field1	 MyIntegerType1     OPTIONAL,
				 field2  MyBooleanType1     DEFAULT TRUE,
				 field3  MyNullType1,
				 field4  MyOctetStringType1 OPTIONAL,
				 field5  MyBitstringType1,
				 field6  MyEnumeratedType2,
				 field7  MyRealType1        OPTIONAL
			   }

MySequenceType4 ::= SEQUENCE  {
				 first INTEGER OPTIONAL,
				 second ENUMERATED {one,two} DEFAULT one

			      }

MySequenceType5 ::= SEQUENCE  {
				COMPONENTS OF 	MySequenceType4,
				new INTEGER
			      }

MySequenceType6 ::= SEQUENCE  {	field1 MyIntegerType1 ,
				field2 MyBooleanType1,
				...!1,
				...,
				field4  MyOctetStringType1
			      }

MySequenceType7 ::= SEQUENCE  {	field1 MyIntegerType1 ,
				field2 MyBooleanType1,
				...!1,
				field6  MyEnumeratedType2,
				...,
				field4  MyOctetStringType1
			      }

MySequenceType8 ::= SEQUENCE  {
				--...!1,
				-- ...,
				field6  MyEnumeratedType2,
				field4  MyOctetStringType1
			      }

MySequenceType9 ::= SEQUENCE  {
				field6  MyEnumeratedType2,
				field4  MyOctetStringType1,
				...!1,
				...
			      }

MySequenceType10 ::= SEQUENCE  {
				field6  MyEnumeratedType2,
				field4  MyOctetStringType1,
				...!1
			      }

MySequenceType11 ::= SEQUENCE  {
				field6  MyEnumeratedType2,
				field4 [1]  MyOctetStringType1

			      }

MySequenceType12 ::= SEQUENCE  {
				field6  MyEnumeratedType2,
				field4 [1] IMPLICIT  MyOctetStringType1

			      }

MySequenceType13 ::= SEQUENCE  {
				field6  MyEnumeratedType2,
				field4 [1] EXPLICIT MyOctetStringType1

			      }

mySequenceValue1 MySequenceType1 ::=  {
  			     field1 555,                            -- INTEGER,
			     field2 TRUE,                            -- BOOLEAN,
			     field3 NULL,
			     field4 'FF00'H,                         -- OCTET STRING,
			     field5 '01010'B,                        -- BIT STRING,
			     field6  a,                             --ENUMERATED {a,b,c},
			     field7  {mantissa 10,base 2, exponent 2}        --REAL
			    }

mySequenceValue3 MySequenceType3 ::=
				{
				 field3  NULL,        --MyNullType1,
				 field5 '0101'B,      --MyBitstringType1,
				 field6  a,           --MyEnumeratedType1,
				 field7 {mantissa 10,base 2, exponent 2}  --MyRealType1  OPTIONAL

			        }

--25 SEQUENCE OF *******************************************************************

MySequenceOfType1 ::= SEQUENCE OF INTEGER

MySequenceOfType2 ::= SEQUENCE OF MyBooleanType1

MySequenceOfType3 ::= SEQUENCE OF MySequenceOfType1

MySequenceOfType4 ::= SEQUENCE OF MySequenceOfType2

mySequenceOfValue1 MySequenceOfType1 ::= {}

mySequenceOfValue2 MySequenceOfType1 ::= {5,1000,3}

mySequenceOfValue3 MySequenceOfType2 ::= {TRUE,FALSE}

mySequenceOfValue4 MySequenceOfType3 ::={
					 {5,1000,3,7},
					 {4,1001,3},
					 {5,1000,3,333,9,3}
					}

mySequenceOfValue5 MySequenceOfType4 ::=
					{
					{TRUE,FALSE,FALSE},
					{TRUE,FALSE,FALSE,FALSE},
					{TRUE,FALSE,TRUE,TRUE,TRUE,TRUE}

					}

--26 SET *******************************************************************

MySetType0 ::= SET {}

MySetType1 ::= SET {
  			     field1 INTEGER,
			     field2 BOOLEAN,
			     field3 NULL,
			     field4 OCTET STRING,
			     field5 BIT STRING,
			     field6 ENUMERATED {a,b,c},
			     field7 REAL,
			     field8 MySequenceType1
			    }

MySetType2 ::= SET  {
				 field1	 MyIntegerType1,
				 field2  MyBooleanType1,
				 field3  MyNullType1,
				 field4  MyOctetStringType1,
				 field5  MyBitstringType1,
				 field6  MyEnumeratedType2,
				 field7  MyRealType1,
				 field8  MySequenceType1
			   }

MySetType3 ::= SET  {
				 field1	 MyIntegerType1     OPTIONAL,
				 field2  MyBooleanType1     DEFAULT TRUE,
				 field3  MyNullType1,
				 field4  MyOctetStringType1 OPTIONAL,
				 field5  MyBitstringType1,
				 field6  MyEnumeratedType2,
				 field7  MyRealType1        OPTIONAL,
				 field8  MySequenceType1
			   }

MySetType4 ::= SET            {
				 first INTEGER OPTIONAL,
				 second ENUMERATED {one,two} DEFAULT one

			      }

MySetType5 ::= SET  {
				COMPONENTS OF 	MySetType4,
				new INTEGER
			      }

MySetType6 ::= SET  {	field1 MyIntegerType1 ,
				field2 MyBooleanType1,
				...!1,
				...,
				field4  MyOctetStringType1
			      }

MySetType7 ::= SET {	field1 MyIntegerType1 ,
				field2 MyBooleanType1,
				...!1,
				field6  MyEnumeratedType2,
				...,
				field4  MyOctetStringType1
			      }

MySetType8 ::= SET  {
				--...!1,
				--...,
				field6  MyEnumeratedType2,
				field4  MyOctetStringType1
			      }

MySetType9 ::= SET  {
				field6  MyEnumeratedType2,
				field4  MyOctetStringType1,
				...!1,
				...
			      }

MySetType10 ::= SET {
				field6  MyEnumeratedType2,
				field4  MyOctetStringType1,
				...!1
			      }

MySetType11 ::= SET {
				field6  MyEnumeratedType2,
				field4  [0] MyOctetStringType1

			      }
MySetType12 ::= SET {
				field6  MyEnumeratedType2,
				field4  [0] IMPLICIT MyOctetStringType1

			      }
MySetType13 ::= SET {
				field6  MyEnumeratedType2,
				field4  [0] EXPLICIT MyOctetStringType1

			      }

mySetValue1 MySetType1 ::=  {
  			     field1 555,                            -- INTEGER,
			     field2 TRUE,                            -- BOOLEAN,
			     field3 NULL,
			     field4 'FF00'H,                         -- OCTET STRING,
			     field5 '01010'B,                        -- BIT STRING,
			     field6  a,                              --ENUMERATED {a,b,c),
			     field7  {mantissa 10,base 2, exponent 2},        --REAL
			     field8  mySequenceValue1
			    }

mySetValue3 MySetType3 ::=

				{
				 field3  NULL,        --MyNullType1,
				 field5 '0101'B,      --MyBitstringType1,
				 field6  a,           --MyEnumeratedType1,
				 field7 {mantissa 10,base 2, exponent 2},  --MyRealType1  OPTIONAL
			         field8  mySequenceValue1
				}

--27 SET OF *******************************************************************

MySetOfType1 ::= SET OF INTEGER

MySetOfType2 ::= SET OF MyBooleanType1

MySetOfType3 ::= SET OF MySequenceOfType1

MySetOfType4 ::= SET OF MySequenceOfType2

mySetOfValue1 MySetOfType1 ::= {}

mySetOfValue2 MySetOfType1 ::= {5,1000,3}

mySetOfValue3 MySetOfType2 ::= {TRUE,FALSE}

mySetOfValue4 MySetOfType3 ::={
					 {5,1000,3,7},
					 {4,1001,3},
					 {5,1000,3,333,9,3}
					}

mySetOfValue5 MySequenceOfType4 ::=
					{
					{TRUE,FALSE,FALSE},
					{TRUE,FALSE,FALSE,FALSE},
					{TRUE,FALSE,TRUE,TRUE,TRUE,TRUE}

					}

--28 CHOICE *******************************************************************

MyChoiceType1 ::= CHOICE
			    {
  			     field1 INTEGER,
			     field2 BOOLEAN,
			     field3 NULL,
			     field4 OCTET STRING,
			     field5 BIT STRING,
			     field6 ENUMERATED {a,b,c},
			     field7 REAL,
			     field8 MySequenceType1
			    }

MyChoiceType2 ::= CHOICE {
  			     field1 INTEGER,
			     field2 BOOLEAN,
			     field3 NULL,
			     field4 OCTET STRING,
			     field5 BIT STRING,
			     ...!1,
			     field6 ENUMERATED {a,b,c},
			     field7 REAL,
			     field8 MySequenceType1,
			     ...
			    }

MyChoiceType3 ::= CHOICE  {
  			     field1 INTEGER,
			     field2 BOOLEAN,
			     field3 NULL,
			     field4 OCTET STRING,
			     field5 BIT STRING,
			     ...!1,
			     field6 ENUMERATED {a,b,c},
			     field7 REAL,
			     field8 MySequenceType1
			    }

MyChoiceType4 ::= CHOICE {
 			     field1 INTEGER,
			     field2 BOOLEAN,
			     ...,
			     [[ field3 NULL,
			     field4 OCTET STRING,
			     field5 BIT STRING]],
			     field6 ENUMERATED {a,b,c},
			     field7 REAL,
                             field8 MySequenceType1
			    }

MyChoiceType5 ::= CHOICE {
 			     field1 INTEGER,
			     field2 BOOLEAN,
			     ...,
			     [[ field3 NULL,
			     field4 OCTET STRING,
			     field5 BIT STRING]],
			     field6 ENUMERATED {a,b,c},
			     field7 REAL,
                             field8 MySequenceType1,
                             ...
			    }

MyChoiceType6 ::= CHOICE  {
  			     field1 [0] INTEGER,
			     field2 BOOLEAN,
			     field3 NULL,
			     field4 OCTET STRING,
			     field5 [3] BIT STRING,
			     field6 ENUMERATED {a,b,c},
			     field7 REAL,
			     field8 MySequenceType1
			    }

myChoiceValue1  MyChoiceType1 ::=   field1 : 1234

myChoiceValue2  MyChoiceType2 ::=   field2 : TRUE

myChoiceValue3  MyChoiceType3 ::=   field6 : a

myChoiceValue4  MyChoiceType4 ::=   field7 : { mantissa 314159,base 10, exponent -10 }

myChoiceValue5  MyChoiceType1 ::= field8 : {

  			     field1 555,
			     field2 FALSE,
			     field3 NULL,
			     field4 'FF00'H,
			     field5 '01010'B,
			     field6  a,
			     field7  {mantissa 10,base 2, exponent 2}

			    }
--29 SELECTION TYPES *******************************************************************

--MySelectionType ::= field1 < MyChoiceType1
--COMMENT

-- MySelectionValue MySelectionType ::= 123
--COMMENT

--30 Tagged Types *******************************************************************

MyTaggedtype1 ::= [ UNIVERSAL 0] MySequenceType1
--COMMENT

MyTaggedtype2 ::= [ APPLICATION 0] MySequenceType1

MyTaggedtype3 ::= [ PRIVATE 0] MySequenceType1

MyTaggedtype4 ::= [ 0 ] MySequenceType1

MyTaggedtype5 ::= [ UNIVERSAL 0 ] IMPLICIT MySequenceType1
--COMMENT

MyTaggedtype6 ::= [ APPLICATION 0] IMPLICIT  MySequenceType1

MyTaggedtype7 ::= [ PRIVATE 0] IMPLICIT  MySequenceType1

MyTaggedtype8 ::= [ 0 ] IMPLICIT  MySequenceType1

MyTaggedtype9 ::= [ UNIVERSAL 0] EXPLICIT MySequenceType1
--COMMENT

MyTaggedtype10 ::= [ APPLICATION 0] EXPLICIT  MySequenceType1

MyTaggedtype11 ::= [ PRIVATE 0] EXPLICIT  MySequenceType1

MyTaggedtype12 ::= [ 0 ] EXPLICIT  MySequenceType1

--31 OBJECT IDENTIFIER *******************************************************************

MyObjectIdentifierType1 ::= OBJECT IDENTIFIER

ericsson OBJECT IDENTIFIER ::= { itu-t(0) identified-organization(4) etsi(0) reserved(127)
etsi-identified-organization(0) ericsson(5) }

myObjectIdentifierValue1   MyObjectIdentifierType1 ::= {abcd(1) efgh(2) ijkl(3) mnop(4) qrst(5) uvwx(6) yz(1111) }

myObjectIdentifierValue2   MyObjectIdentifierType1 ::= {1 2 3 4 5 6 }

myObjectIdentifierValue3   MyObjectIdentifierType1 ::= {abcd(1) efgh(2) ijkl(3) mnop(4) qrst(5) uvwx(6) yz(1111) }

--32 RELATIVE OBJECT IDENTIFIER *******************************************************************

myRelativeOIDvalue1 RELATIVE-OID ::=  { 9 8 7 6 5 4 3 2 1 0 }

myRelativeOIDvalue2 RELATIVE-OID ::=  { first(9) second(8) third(7) a(6) b(5) c(4) d(3) e(2) f(1) g(0) }

MyRelativeOIDType1 ::= RELATIVE-OID

myRelativeOIDValue3 MyRelativeOIDType1 ::= { 12 34 56 78 90 }

myRelativeOIDValue4 MyRelativeOIDType1 ::= { x(0) y(1) z(2)}

/*
--33 EMBEDDED PDV *******************************************************************
-- COMMENT ENTIRE SECTION

MyEmbeddedPDVType1 ::= EMBEDDED PDV

myEmbeddedPDVValue1 MyEmbeddedPDVType1 ::=
{

identification syntaxes :
			{
			 abstract {qw(0) er(0) ty(3)},
			 transfer myObjectIdentifierValue1
			},
data-value '1234567890ABCDEF'H

}

myEmbeddedPDVValue2 MyEmbeddedPDVType1 ::=
{

identification syntax : myObjectIdentifierValue2,

data-value '1234567890ABCDEF'H

}

myEmbeddedPDVValue3 MyEmbeddedPDVType1 ::=
{

identification presentation-context-id : myIntegerValue1,

data-value '1234567890ABCDEF'H

}

myEmbeddedPDVValue4 MyEmbeddedPDVType1 ::=
{

identification context-negotiation : {
				presentation-context-id   333,
				transfer-syntax { asdf(9) dfghj(6) }
				   },

data-value '1234567890ABCDEF'H

}

myEmbeddedPDVValue5 MyEmbeddedPDVType1 ::=
{

identification transfer-syntax : {0 0 0 0 0 0},

data-value '1234567890ABCDEF'H

}

myEmbeddedPDVValue6 MyEmbeddedPDVType1 ::=
{

identification fixed : NULL

data-value '1234567890ABCDEF'H

}

--34 EXTERNAL *******************************************************************
-- COMMENT ENTIRE SECTION
MyExternalType1 ::= EXTERNAL

myExternalValue1 MyExternalType1::=

{
identification syntax : {0 1 2 3 4 5},

data-value-descriptor myObjectDescriptorValue1,

data-value '1234567890ABCDEF'H

}

myExternalValue2 MyExternalType1 ::=

{
identification presentation-context-id : 5,

data-value-descriptor myObjectDescriptorValue1,

data-value '1234567890ABCDEF'H

}

myExternalValue3 MyExternalType1 ::=

{
identification context-negotiation {
				presentation-context-id   333,
				transfer-syntax { asdf(9) dfghj(6) }
				   },

data-value-descriptor myObjectDescriptorValue1,

data-value '1234567890ABCDEF'H

}
*/
-- 35 (37) character string (restricted) *******************************************************************
-- planned to be supported : IA5String, ISO646String, NumericString, PrintableString, Visible String

-- planned for later implementation :BMPString, GeneralString, GraphicString,TeletexString, T61String,
-- UniversalString, UTF8STring, VideotexString,

--  cstring of IA5String is currently supported

myIA5StringValue1 IA5String ::=
"abcdefghijklmnopqrstuvwxyz
ABCDEFGHIJKLMNOPQRSTUVWXYZ
0123456789 add the control characters too"      -- cstring format

myIA5StringValue2 IA5String ::= {3,4}           -- tuple format

myIA5StringValue3 IA5String ::= {1, 1, 1, 1 }   -- quadruple format

myIA5StringValue4 IA5String ::= { "qwerty", {0 , 1}, { 0 , 0 , 0 , 0}, "uiop"  }  --character string list

myIA5StringValue5 IA5String ::= { "abcd", myIA5StringValue4, myIA5StringValue3, myIA5StringValue2, myIA5StringValue1 }

myISO646StringValue1 ISO646String ::= "       "    --cstring format

myNumericStringValue1 NumericString ::= "0123456789  " --cstring format

myPrintableStringValue1  PrintableString ::=
"abcdefghijklmnopqrstuvwxyzABCDEFGHIJKLMNOPQRSTUVWXYZ0123456789 '()+,-./:=? "    --cstring format

myVisibleString  VisibleString ::= "         "

-- 40 UNRESTRICTED CHARACTER TYPE *******************************************************************

MyUnrestrictedCharacterType ::= CHARACTER STRING

myUnrestrictedCharacterValue1 MyUnrestrictedCharacterType ::= {

							identification syntaxes :
								{
			                                    abstract {qw(0) er(0) ty(3)},
			                                    transfer myObjectIdentifierValue1
			                                         },

							string-value '0123456789ABCDEF'H

							}

myUnrestrictedCharacterValue2 MyUnrestrictedCharacterType ::= {

							identification syntax {0 2 66 5},

							string-value '0123456789ABCDEF'H
							}

myUnrestrictedCharacterValue3 MyUnrestrictedCharacterType ::= {

							identification presentation-context-id : 77,

							string-value '0123456789ABCDEF'H

							}

myUnrestrictedCharacterValue4 MyUnrestrictedCharacterType ::= {

							identification context-negotiation :
							        {
				                              presentation-context-id   333,
				                              transfer-syntax { asdf(9) dfghj(6) }
				                                },

							string-value '0123456789ABCDEF'H

								}

myUnrestrictedCharacterValue5 MyUnrestrictedCharacterType ::= {

							identification transfer-syntax : { fgh (0) nvk(4) }

							string-value '0123456789ABCDEF'H

								}

myUnrestrictedCharacterValue6 MyUnrestrictedCharacterType ::= {

							identification fixed : NULL

							string-value '0123456789ABCDEF'H

								}
-- 42 GENERALIZED TIME *******************************************************************
-- COMMENT ENTIRE SECTION

MyGeneralizedTimeType1 ::= GeneralizedTime

myGeneralizedTimeValue1 MyGeneralizedTimeType1 ::= "20030529151410.4"

myGeneralizedTimeValue2 MyGeneralizedTimeType1 ::= "20030529151410.4Z"

myGeneralizedTimeValue3 MyGeneralizedTimeType1 ::= "20030529151410.4 -0500"

-- 43 UNIVERSAL TIME  *******************************************************************

MyUniversalTimeType1 ::= UTCTime

myUniversalTImeValue1 MyUniversalTimeType1::= "0305291514Z"

myUniversalTImeValue2 MyUniversalTimeType1::= "0305291514-0500"

-- 44 OBJECT DESCRIPTOR  *****************************************************************

MyObjectDescriptorType1 ::= ObjectDescriptor

-- MyObjectDescriptorvalue ::= "  "
-- should be graphicstring

-- 45 CONSTRAINED TYPES *******************************************************************
-- mi ez?

-- 46 ELEMENT SET SPECIFICATION  **********************************************************

MyElementSetType1 ::= INTEGER (ALL EXCEPT (0..15))

MyElementSetType2 ::= INTEGER (0..1|4..6)

MyElementSetType3 ::= INTEGER (0..7^5..10)

MyElementSetType4 ::= INTEGER (0..1 UNION 4..6)

MyElementSetType5 ::= INTEGER (0..7 INTERSECTION 5..10)

MyElementSetType6 ::= IA5String("yes"|"no")

MyElementSetType7-CapitalA ::= IA5String ( FROM ("A"))

MyElementSetType8-String1   ::= IA5String ( FROM ("A".. "Z") UNION FROM ("a".. "z"))

MyElementSetType9-String2   ::= IA5String ( FROM ("A".. "Z" UNION "a".. "z"))

MyElementSetType10 ::= INTEGER (0|1|4|6)

MyElementSetType11 ::= BIT STRING { bit0 (0), bit1 (1) } (SIZE (8)) (ALL EXCEPT {})

MyElementSetType12 ::= BIT STRING { bit0 (0), bit1 (1) } (SIZE (8)) (ALL EXCEPT { bit0 })

MyElementSetType13 ::= BIT STRING { bit0 (0), bit1 (1) } (SIZE (8)) (ALL EXCEPT { bit1 })

MyElementSetType14 ::= BIT STRING { bit0 (0), bit1 (1) } (SIZE (8)) (ALL EXCEPT { bit0, bit1 })

-- 46 SUBTYPE ELEMENTS  *******************************************************************
-- to be added later

END
