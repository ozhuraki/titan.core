--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--   Szabo, Janos Zoltan – initial implementation
--
--/////////////////////////////////////////////////////////////////////////////
Test3  -- X.682

DEFINITIONS

AUTOMATIC TAGS

::=

BEGIN
--*************************************************************
-- USER DEFINED CONSTRAINTS ***********************************
--*************************************************************

MyEncryptedType0  ::= BIT STRING (CONSTRAINED BY
{Type-to-be-encrypted})

MyEncryptedType1 {Type-to-be-encrypted} ::= BIT STRING (CONSTRAINED BY
{Type-to-be-encrypted})

MyEncryptedType2 {Type-to-be-encrypted} ::= BIT STRING (CONSTRAINED BY
{Type-to-be-encrypted} -- comments, comments comments --)

MyEncryptedType3 {Type-to-be-encrypted} ::= BIT STRING (CONSTRAINED BY
{-- comments -- Type-to-be-encrypted-- comments, comments comments --} )

MyEncryptedType4 {Type-to-be-encrypted1, Type-to-be-encrypted2, Type-to-be-encrypted3} ::= BIT STRING (CONSTRAINED BY
{Type-to-be-encrypted,Type-to-be-encrypted2,Type-to-be-encrypted3 })

MyEncryptedType5 {CLASS-TO-BE-USED} ::= BIT STRING (CONSTRAINED BY
{CLASS-TO-BE-USED})

MyEncryptedType6 {GovernorType1 : par-value} ::= BIT STRING (CONSTRAINED BY
{GovernorType1 : 6})

MyEncryptedType7 {GovernorType1 : par-value} ::= BIT STRING (CONSTRAINED BY
{GovernorType1 : {5,4,3,2,1} })

MyEncryptedType8 {MY-CLASS-1 : par-object} ::= BIT STRING (CONSTRAINED BY
{MY-CLASS-1 : myObject-1})

MyEncryptedType9 {MY-CLASS-1 : par-object-set} ::= BIT STRING (CONSTRAINED BY
{MY-CLASS-1 : MyInformationObjectSet1})

MyEncryptedType10  ::= BIT STRING (CONSTRAINED BY
{Type-to-be-encrypted} ! -4)

MyEncryptedType11  ::= BIT STRING (CONSTRAINED BY
{Type-to-be-encrypted} ! BIT STRING : '01'B)

MyEncryptedType12  ::= BIT STRING (CONSTRAINED BY
{Type-to-be-encrypted} ! myEncryptedValue0)

myEncryptedValue0 MyEncryptedType0  ::= '000001111100000'B

myEncryptedValue1 MyEncryptedType1 { ASN1-Type4 } ::= '000001111100000'B

myEncryptedValue2 MyEncryptedType2 { ASN1-Type4 } ::= '000001111100000'B

myEncryptedValue3 MyEncryptedType3 { ASN1-Type2 } ::= '000001111100000'B

myEncryptedValue4 MyEncryptedType4 { ASN1-Type2 ,ASN1-Type3, ASN1-Type4 }::= '000001111100000'B

myEncryptedValue5 MyEncryptedType5 { MY-CLASS-1 } ::= '000001111100000'B

myEncryptedValue6 MyEncryptedType6 {6} ::= '000001111100000'B

myEncryptedValue7 MyEncryptedType7 {3} ::= '000001111100000'B

myEncryptedValue8 MyEncryptedType8 { myObject-1 }::= '000001111100000'B

myEncryptedValue9 MyEncryptedType9 {{MyInformationObjectSet1}} ::= '000001111100000'B

MY-CLASS-1 ::= CLASS
{
&TypeField OPTIONAL,
&TypeField2 ,
&fixedTypeValueField            ASN1-Type1   UNIQUE OPTIONAL,
&fixedTypeValueField2           ASN1-Type1
}
WITH SYNTAX
{
[TYPE FIELD	                &TypeField]
 TYPE FIELDB	                &TypeField2
[FIXED VALUE TYPE FIELD		&fixedTypeValueField]
 FIXED VALUE TYPE FIELDB	&fixedTypeValueField2
}

myObject-1 MY-CLASS-1 ::=
{
TYPE FIELD                   ASN1-Type3
TYPE FIELDB                  ASN1-Type4
FIXED VALUE TYPE FIELD         999
FIXED VALUE TYPE FIELDB         493
}

myObject-2 MY-CLASS-1 ::=
{
TYPE FIELD	            ASN1-Type2
TYPE FIELDB                 ASN1-Type1
FIXED VALUE TYPE FIELD		888
FIXED VALUE TYPE FIELDB 	395
}

MyInformationObjectSet1 MY-CLASS-1 ::=
{
myObject-1|
myObject-2,
...
}

Type-to-be-encrypted ::= ENUMERATED {a,b,c}

Type-to-be-encrypted2 ::= INTEGER

Type-to-be-encrypted3 ::= BIT STRING

GovernorType1 ::= INTEGER

ASN1-Type1 ::= INTEGER

ASN1-Type2 ::= BOOLEAN

ASN1-Type3 ::= BIT STRING

ASN1-Type4 ::= SEQUENCE {f1 INTEGER, f2 BOOLEAN}

--*************************************************************
-- TABLE CONSTRAINTS ******************************************
--*************************************************************

MyExampleSequenceForTableConstraint ::= SEQUENCE
{
field1      MY-CLASS-1.&fixedTypeValueField ,
field2      MY-CLASS-1.&fixedTypeValueField2,
field3      MY-CLASS-1.&TypeField,
field4      MY-CLASS-1.&TypeField,
field5      MY-CLASS-1.&fixedTypeValueField ({ MyInformationObjectSet1 }) ,
field6      MY-CLASS-1.&fixedTypeValueField2 ({ MyInformationObjectSet1 }),
field7      MY-CLASS-1.&fixedTypeValueField ({ MyInformationObjectSet1 }),
field8      MY-CLASS-1.&fixedTypeValueField2 ({ MyInformationObjectSet1 }),
field9      MY-CLASS-1.&fixedTypeValueField ({ MyInformationObjectSet1 } {@.field2}) ,
field10      MY-CLASS-1.&fixedTypeValueField2 ({ MyInformationObjectSet1 } {@.field2}),
field11      MY-CLASS-1.&fixedTypeValueField ({ MyInformationObjectSet1 } {@.field2}),
field12      MY-CLASS-1.&fixedTypeValueField2 ({ MyInformationObjectSet1 } {@.field2}),
field13      MY-CLASS-1.&fixedTypeValueField ({ MyInformationObjectSet1 } {@field2}) ,
field14      MY-CLASS-1.&fixedTypeValueField2 ({ MyInformationObjectSet1 } {@field2}),
field15      MY-CLASS-1.&fixedTypeValueField ({ MyInformationObjectSet1 } {@field2}),
field16      MY-CLASS-1.&fixedTypeValueField2 ({ MyInformationObjectSet1 } {@field2}),

field17      SEQUENCE{f1 MY-CLASS-1.&fixedTypeValueField ({ MyInformationObjectSet1 } {@.f2}),
                      f2 INTEGER},

field18      SEQUENCE{f11 MY-CLASS-1.&fixedTypeValueField ({ MyInformationObjectSet1 } {@field1}),
                      f22 SEQUENCE{f1 BOOLEAN}},

field19      SEQUENCE{f11 MY-CLASS-1.&fixedTypeValueField ({ MyInformationObjectSet1 } {@.f22.f1}),
                      f22 SEQUENCE{f1 BOOLEAN}},

field20      SEQUENCE{f111 MY-CLASS-1.&fixedTypeValueField ({ MyInformationObjectSet1 } {@field17.f2}),
                      f222 INTEGER},

field21      SEQUENCE{f1111 MY-CLASS-1.&fixedTypeValueField ({ MyInformationObjectSet1 } {@field18.f22.f1}),
                      f2222 INTEGER},

field22      CHOICE {f3 MY-CLASS-1.&fixedTypeValueField ({ MyInformationObjectSet1 } {@.f4}),
                      f4 INTEGER},

field23      CHOICE {f33 MY-CLASS-1.&fixedTypeValueField ({ MyInformationObjectSet1 } {@field1}),
                      f44 SEQUENCE{f1 BOOLEAN}},

field24      CHOICE {f33 MY-CLASS-1.&fixedTypeValueField ({ MyInformationObjectSet1 } {@.f44.f1}),
                      f44 SEQUENCE{f1 BOOLEAN}},

field25      CHOICE {f333 MY-CLASS-1.&fixedTypeValueField ({ MyInformationObjectSet1 } {@field22.f4}),
                       f444 INTEGER},

field26      CHOICE {f3333 MY-CLASS-1.&fixedTypeValueField ({ MyInformationObjectSet1 } {@field23.f44.f1}),
                      f4444 INTEGER},

field27      SET{f5 MY-CLASS-1.&fixedTypeValueField ({ MyInformationObjectSet1 } {@.f6}),
                      f6 INTEGER},

field28      SET{f55 MY-CLASS-1.&fixedTypeValueField ({ MyInformationObjectSet1 } {@field1}),
                      f66 SEQUENCE{f1 BOOLEAN}},

field29      SET{f55 MY-CLASS-1.&fixedTypeValueField ({ MyInformationObjectSet1 } {@.f66.f1}),
                      f66 SEQUENCE{f1 BOOLEAN}},

field30      SET{f555 MY-CLASS-1.&fixedTypeValueField ({ MyInformationObjectSet1 } {@field27.f6}),
                      f666 INTEGER},

field31      SET{f5555 MY-CLASS-1.&fixedTypeValueField ({ MyInformationObjectSet1 } {@field18.f66.f1}),
                      f6666 INTEGER},

field32      SEQUENCE  {
                         f1 CHOICE
                                   {
				   f11	SET {f111 INTEGER, f222 BOOLEAN},
				   f12  INTEGER
	      	                   },

                         f2  MY-CLASS-1.&fixedTypeValueField ({ MyInformationObjectSet1 } {@field32.f1.f11.f111} )
		       },

field33      MY-CLASS-1.&fixedTypeValueField ({ MyInformationObjectSet1 } {@field32.f1.f11.f111 , @field27.f6}),

field34      MY-CLASS-1.&TypeField ({ MyInformationObjectSet1 }),

field35      MY-CLASS-1.&TypeField ({ MyInformationObjectSet1 }  {@.field5}),

field36      MY-CLASS-1.&TypeField ({ MyInformationObjectSet1 }  {@.field5, @.field6}),

field37      MY-CLASS-1.&TypeField ({ MyInformationObjectSet1 }  {@.field5, @.field6} ! -4),

field38      MY-CLASS-1.&TypeField ({ MyInformationObjectSet1 }  {@.field5, @.field6} ! BIT STRING : '01'B),

field39      MY-CLASS-1.&TypeField ({ MyInformationObjectSet1 }  {@.field5, @.field6} ! myEncryptedValue0)

}
--*************************************************************
-- CONTENTS CONSTRAINTS ***************************************
--*************************************************************

MyContentsConstraintType1 ::= OCTET STRING (CONTAINING ASN1-Type4)

MyContentsConstraintType2 ::= OCTET STRING (ENCODED BY {
itu-t (0) identified-organization (4) etsi (0) mobileDomain (0)
umts-Access (20) modules (3) ranap (0) version1 (1) ranap-CommonDataTypes (3)  })

MyContentsConstraintType3 ::= OCTET STRING (CONTAINING ASN1-Type4 ENCODED BY {
itu-t (0) identified-organization (4) etsi (0) mobileDomain (0)
umts-Access (20) modules (3) ranap (0) version1 (1) ranap-CommonDataTypes (3)  })

MyContentsConstraintType4 ::= BIT STRING (CONTAINING ASN1-Type4)

MyContentsConstraintType5 ::= BIT STRING (ENCODED BY {
itu-t (0) identified-organization (4) etsi (0) mobileDomain (0)
umts-Access (20) modules (3) ranap (0) version1 (1) ranap-CommonDataTypes (3)  })

MyContentsConstraintType6 ::= BIT STRING (CONTAINING ASN1-Type4 ENCODED BY {
itu-t (0) identified-organization (4) etsi (0) mobileDomain (0)
umts-Access (20) modules (3) ranap (0) version1 (1) ranap-CommonDataTypes (3)  })

MyContentsConstraintType7 ::= BIT STRING (CONTAINING ASN1-Type4 ENCODED BY {
itu-t (0) identified-organization (4) etsi (0) mobileDomain (0)
umts-Access (20) modules (3) ranap (0) version1 (1) ranap-CommonDataTypes (3)  } ! -4 )

MyContentsConstraintType8 ::= BIT STRING (CONTAINING ASN1-Type4 ENCODED BY {
itu-t (0) identified-organization (4) etsi (0) mobileDomain (0)
umts-Access (20) modules (3) ranap (0) version1 (1) ranap-CommonDataTypes (3)  } ! BIT STRING : '01'B)

MyContentsConstraintType9 ::= BIT STRING (CONTAINING ASN1-Type4 ENCODED BY {
itu-t (0) identified-organization (4) etsi (0) mobileDomain (0)
umts-Access (20) modules (3) ranap (0) version1 (1) ranap-CommonDataTypes (3)  } ! myEncryptedValue0)

END
