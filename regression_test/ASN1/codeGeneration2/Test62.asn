--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Raduly, Csaba
--
--/////////////////////////////////////////////////////////////////////////////
Test62

DEFINITIONS

AUTOMATIC TAGS

::=

BEGIN

IMPORTS ; -- nothing

MyRealType1 ::= REAL

myRealValue1 REAL ::= {mantissa 314159,base 10, exponent -10}

myRealValue2 MyRealType1 ::= {mantissa 314159,base 10, exponent -5}

myMantissa INTEGER ::= 123

myBase INTEGER ::= 2

myExponent INTEGER ::= 0

myRealValue3 MyRealType1 ::= {mantissa myMantissa ,base myBase, exponent myExponent}

myRealValue4 REAL ::= {mantissa myMantissa ,base 10, exponent myExponent}



END
