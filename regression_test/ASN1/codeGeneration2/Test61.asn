--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Raduly, Csaba
--
--/////////////////////////////////////////////////////////////////////////////
Test61

DEFINITIONS

AUTOMATIC TAGS

::=

BEGIN

IMPORTS ; -- nothing

MyIntegerType1 ::= INTEGER { firstnumber(-1000), secondnumber(0), othernumber(1000), lastnumber (-999) }

myIntegerValue1 MyIntegerType1 ::= firstnumber

myIntegerValue2 MyIntegerType1 ::= secondnumber

myIntegerValue3 MyIntegerType1 ::= othernumber

myIntegerValue4 MyIntegerType1 ::= lastnumber



MyIntegerType2 ::= INTEGER {first(myIntegerValue1), second(myIntegerValue2),other(myIntegerValue3), last(myIntegerValue4) }

myIntegerValue5 MyIntegerType2 ::= first

myIntegerValue6 MyIntegerType2 ::= second

myIntegerValue7 MyIntegerType2 ::= other

myIntegerValue8 MyIntegerType2 ::= last

END
