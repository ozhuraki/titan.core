--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--   Szabo, Janos Zoltan – initial implementation
--
--/////////////////////////////////////////////////////////////////////////////
Test34
DEFINITIONS

IMPLICIT TAGS

::=

BEGIN

MySequenceType ::= SEQUENCE {
  			     field1 [0] INTEGER,
			     field2 [1] BOOLEAN DEFAULT TRUE,
			     field3 [2] NULL OPTIONAL,
			     field4 [3] OCTET STRING DEFAULT 'FFFF'H,
			     ...,
			     field5 [1] BIT STRING ,
			     field6 [4] ENUMERATED {a,b,c} OPTIONAL,
			     field7 [5] REAL
			    }

END
