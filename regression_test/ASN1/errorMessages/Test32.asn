--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--
--/////////////////////////////////////////////////////////////////////////////
Test32
DEFINITIONS

IMPLICIT TAGS

::=

BEGIN

MySequenceType ::= SEQUENCE {
  			     field1  INTEGER,
			     field2 [0] BOOLEAN OPTIONAL,
			     field3 [0] NULL OPTIONAL,
			     field4 [1] OCTET STRING OPTIONAL,
			     field5 [2] BIT STRING ,
			     field6 [3] ENUMERATED {a,b,c} OPTIONAL,
			     field7 [4] REAL
			    }

END
