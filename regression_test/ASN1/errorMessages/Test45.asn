--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Szabados, Kristof
--
--/////////////////////////////////////////////////////////////////////////////
Test45
DEFINITIONS

IMPLICIT TAGS

::=

BEGIN

redefinedValue OCTETSTRING ::= '0123456789ABCDEF'H

redefinedValue BIT STRING ::= 'ABCDEF0123456789'H

END
