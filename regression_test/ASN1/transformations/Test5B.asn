--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Koppany, Csaba
--   Kulcsar, Endre
--   Raduly, Csaba
--   Szabados, Kristof
--
--/////////////////////////////////////////////////////////////////////////////
Test5B -- extensibility implied B
DEFINITIONS

AUTOMATIC TAGS


::=

BEGIN

IMPORTS ; -- nothing

MySequenceType1 ::= SEQUENCE
		{
		field1 INTEGER,
		field2 BOOLEAN,
		...
		}

MySetType1 ::= SET
		{
		field1 INTEGER,
		field2 BOOLEAN,
		...
		}

MyEnumeratedType ::= ENUMERATED
		{
			option1,
			option2,
			...
		}

MyChoiceType ::= CHOICE
		{
		field1 INTEGER,
		field2 BOOLEAN,
		...
		}



END
