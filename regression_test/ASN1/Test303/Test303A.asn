--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kovacs, Ferenc
--   Kulcsar, Endre
--   Raduly, Csaba
--   Szabados, Kristof
--
--/////////////////////////////////////////////////////////////////////////////
Test303A

DEFINITIONS

::=

BEGIN

IMPORTS ; -- nothing

MyBitstringType1 ::= BIT STRING { first(0), other (5) }

myBitstringValue1 MyBitstringType1 ::=
 {first, other } --'100001'B

myGeneralStringValue1 GeneralString ::= "General"

END
