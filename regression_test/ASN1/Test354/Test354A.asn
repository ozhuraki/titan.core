--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Kulcsar, Endre
--   Raduly, Csaba
--   Szabados, Kristof
--
--/////////////////////////////////////////////////////////////////////////////
Test354A
DEFINITIONS

AUTOMATIC TAGS

::=

BEGIN


IMPORTS ; -- nothing

MySequenceType2 ::= SEQUENCE {
  			     field1 INTEGER,
			     field2 BOOLEAN,
			    -- field3 NULL,
			     field4 OCTET STRING,
			     field5 BIT STRING,
			     field6 ENUMERATED {a1,b1,c1}
			   --  field7 REAL   NOT SUPP
			    }



MySetType2 ::= SET{
  			     field1 INTEGER,
			     field2 BOOLEAN,
			    -- field3 NULL,
			     field4 OCTET STRING,
			     field5 BIT STRING,
			     field6 ENUMERATED {a2,b2,c2}
			    -- field7 REAL   NOT SUPP
			    }
MyChoiceType2 ::= CHOICE{
  			     field1 INTEGER,
			     field2 BOOLEAN,
			   --  field3 NULL,
			     field4 OCTET STRING,
			     field5 BIT STRING,
			     field6 ENUMERATED {a3,b3,c3}
			    --  field7 REAL NOT SUPP
			    }







MySetType ::= SET

   {
   field1  INTEGER,
   field2  BOOLEAN,
   field3  BIT STRING OPTIONAL,
   field4  OCTET STRING DEFAULT 'FF00'H ,
   field5  MySequenceType2,
   field6  MySetType2,
   field7  MyChoiceType2
   }


mySetValue1A MySetType ::=
   {

   field2 TRUE,
   field1 55,
   field3 '001100'B,
   field4 'FFAAFF'H,
   field5 {
           field1 555,
	   field2 TRUE,
	  -- field3 NULL,
	   field4 'FF00'H,
	   field5 '01010'B,
	   field6  a1
         --  field7  4.5  REAL NOT SUPP

         },
   field6
   {
           field5 '01010'B,
	   field6  b2,
          -- field7  3.5,  REAL NOT SUPP
           field1   444,
	   field2   FALSE,
	 --  field3   NULL,
	   field4   'FFEEDDCCBBAA012345678900'H
   },
   field7 field1 : 5
   }


 mySetValue2A MySetType ::=
   {
   field2 TRUE,
   field1 55,
   field4 'AA'H,
   field5 {
           field1 555,
	   field2 TRUE,
	 --  field3 NULL,
	   field4 'FF00'H,
	   field5 '01010'B,
	   field6  a1
         --  field7  4.5    REAL NOT SUPP

         },
   field6
   {
           field5 '01010'B,
	   field6  b2,
          -- field7  3.5,   REAL NOT SUPP
           field1   444,
	   field2   FALSE,
	  -- field3   NULL,
	   field4   'ABCD012345678900'H
   },
   field7 field1 : 5
   }

 END
