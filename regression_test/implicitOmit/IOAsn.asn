--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Baranyi, Botond
--
--/////////////////////////////////////////////////////////////////////////////
IOAsn
DEFINITIONS

AUTOMATIC TAGS ::= 

BEGIN

AsnSequence ::= SEQUENCE {
  field1 ENUMERATED { enumVal } OPTIONAL,
  field2 CHOICE {
    alt1 INTEGER,
    alt2 INTEGER
  }       OPTIONAL,
  field3 INTEGER OPTIONAL,
  field4 INTEGER OPTIONAL
}


END
