--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Szabo, Bence Janos
--
--/////////////////////////////////////////////////////////////////////////////

Definitions 

DEFINITIONS IMPLICIT TAGS ::=

BEGIN

IMPORTS

  releaseCall-CAPv2
    FROM Imported-Definitions ;

OPERATION ::= CLASS {
  &ArgumentType          ,
  &operationCode         INTEGER UNIQUE
}
WITH SYNTAX {
  [ARGUMENT &ArgumentType]
  [CODE &operationCode]
}

Invoke{OPERATION:Operations} ::= SEQUENCE {
  opcode
    OPERATION.&operationCode
      ({Operations}),
  argument 
    OPERATION.&ArgumentType
      ({Operations}{@opcode})
}

CAPv2-Invoke ::= Invoke{{Supported-CAP-Operations-CAPv2}}

Supported-CAP-Operations-CAPv2 OPERATION ::= {
  releaseCall-CAPv2 
}

END
