--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Baranyi, Botond
--
--/////////////////////////////////////////////////////////////////////////////

ImportedAsn  { iso (1) standard (0) calm-management (24102) iitsscu (4) asnm-1 (1) }

DEFINITIONS AUTOMATIC TAGS ::=

BEGIN
-- EXPORTS <exports clause>;
IMPORTS 
MYREALTYPE FROM ImportingAsn
MYREAL-LOWER FROM ImportedLowerAsn 
;
-- MODULE-BODY
IIC-Request ::= INTEGER
IIC-Response::= INTEGER

IICrequestTX::=IIC-Request
IICresponseTX::=IIC-Response

IICrequestRX::=IIC-Request

IICresponseRX::=IIC-Response

myReal MYREALTYPE ::= 2.0
myReal2 MYREAL-LOWER ::=3.1

END
