--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Szabo, Janos Zoltan – initial implementation
--
--/////////////////////////////////////////////////////////////////////////////
A DEFINITIONS ::=
BEGIN

A1 ::= SEQUENCE {
  f1 BOOLEAN,
  f2 SEQUENCE OF A3
}

A2 ::= SET {
  f1 BIT STRING,
  f2 SET OF A3
}

A3 ::= CHOICE {
  a1 OCTET STRING,
  a2 INTEGER
}

END
