--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Szabados, Kristof
--   Szabo, Janos Zoltan – initial implementation
--
--/////////////////////////////////////////////////////////////////////////////
A DEFINITIONS ::=
BEGIN

OPERATION ::= CLASS {
  &ArgumentType          OPTIONAL,
  &operationCode         INTEGER UNIQUE OPTIONAL
}
WITH SYNTAX {
  [ARGUMENT &ArgumentType]
  [CODE &operationCode]
}
-- TODO: SYNTAX nelkul

Invoke{OPERATION:Operations} ::= SEQUENCE {
  opcode OPERATION.&operationCode ({Operations}),
  argument OPERATION.&ArgumentType ({Operations}{@opcode}) OPTIONAL
}

PARAMETERS-BOUND ::= CLASS {
  &dummy INTEGER
}

cAPSpecificBoundSet PARAMETERS-BOUND ::= {
  &dummy 1
}

Supported-CAP-Operations OPERATION ::= {initialDPSMS{cAPSpecificBoundSet}}

initialDPSMS {PARAMETERS-BOUND : bound} OPERATION ::= {
	ARGUMENT		InitialDPSMSArg {bound}
	CODE		1
}

InitialDPSMSArg{PARAMETERS-BOUND : bound} ::= SEQUENCE {
   f1 INTEGER
}

END
