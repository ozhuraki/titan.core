--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--   Raduly, Csaba
--
--/////////////////////////////////////////////////////////////////////////////
MobileDomainDefinitions {ccitt (0) identified-organization (4) etsi (0)
			 mobileDomain (0) mobileDomainDefinitions (0) version1 (1)}

DEFINITIONS ::=
BEGIN

IMPORTS ;

-- Mobile DomainId

mobileDomainId OBJECT IDENTIFIER ::= {ccitt (0) identified-organization (4) etsi (0) mobileDomain (0)}

-- Mobile Subdomains

gsm-NetworkId OBJECT IDENTIFIER ::= 			{mobileDomainId gsm-Network (1)}
gsm-AccessId OBJECT IDENTIFIER ::= 			{mobileDomainId gsm-Access (2)}
gsm-OperationAndMaintenanceId OBJECT IDENTIFIER ::= 	{mobileDomainId gsm-Operation-Maintenance (3)}
gsm-MessagingId OBJECT IDENTIFIER ::= 			{mobileDomainId gsm-Messaging (4)}

-- Common Component Ids for structuring Mobile Subdomains

CommonComponentId ::= INTEGER (0..9)

ac-Id CommonComponentId ::= 0
as-Id CommonComponentId ::= 1
ase-Id CommonComponentId ::= 2
moduleId CommonComponentId ::= 3
er-Id CommonComponentId ::= 4

END -- MobileDomainDefinitions
