--/////////////////////////////////////////////////////////////////////////////
-- Copyright (c) 2000-2021 Ericsson Telecom AB
-- All rights reserved. This program and the accompanying materials
-- are made available under the terms of the Eclipse Public License v2.0
-- which accompanies this distribution, and is available at
-- https://www.eclipse.org/org/documents/epl-2.0/EPL-2.0.html
--
-- Contributors:
--   Balasko, Jeno
--
--/////////////////////////////////////////////////////////////////////////////
VIRAG
DEFINITIONS

AUTOMATIC TAGS
EXTENSIBILITY IMPLIED

::=

BEGIN

IMPORTS ; 
    
    VIRAG-EXTERNAL ::= [UNIVERSAL 8] IMPLICIT SEQUENCE {
      identification CHOICE {
        syntaxes SEQUENCE {
          abstract OBJECT IDENTIFIER,
          transfer OBJECT IDENTIFIER
        },
        syntax OBJECT IDENTIFIER,
        presentation-context-id INTEGER,
        context-negotiation SEQUENCE {
          presentation-context-id INTEGER,
          transfer-syntax OBJECT IDENTIFIER
        },
        transfer-syntax OBJECT IDENTIFIER,
        fixed NULL
      },
      data-value-descriptor ObjectDescriptor OPTIONAL,
      data-value OCTET STRING
    } (WITH COMPONENTS {
      ...,
      identification (WITH COMPONENTS {
        ...,
        syntaxes        ABSENT,
        transfer-syntax ABSENT,
        fixed           ABSENT
      })
    })

    VIRAG-EMBEDDED-PDV ::= [UNIVERSAL 11] IMPLICIT SEQUENCE {
      identification CHOICE {
        syntaxes SEQUENCE {
          abstract OBJECT IDENTIFIER,
          transfer OBJECT IDENTIFIER
        },
        syntax OBJECT IDENTIFIER,
        presentation-context-id INTEGER,
        context-negotiation SEQUENCE {
          presentation-context-id INTEGER,
          transfer-syntax OBJECT IDENTIFIER
        },
        transfer-syntax OBJECT IDENTIFIER,
        fixed NULL
      },
      data-value-descriptor ObjectDescriptor OPTIONAL,
      data-value OCTET STRING
    } (WITH COMPONENTS {
      ...,
      data-value-descriptor ABSENT
    })

    VIRAG-CHARACTER-STRING ::= [UNIVERSAL 29] IMPLICIT SEQUENCE {
      identification CHOICE {
        syntaxes SEQUENCE {
          abstract OBJECT IDENTIFIER,
          transfer OBJECT IDENTIFIER
        },
        syntax OBJECT IDENTIFIER,
        presentation-context-id INTEGER,
        context-negotiation SEQUENCE {
          presentation-context-id INTEGER,
          transfer-syntax OBJECT IDENTIFIER
        },
        transfer-syntax OBJECT IDENTIFIER,
        fixed NULL
      },
      data-value-descriptor ObjectDescriptor OPTIONAL,
      string-value OCTET STRING
    } (WITH COMPONENTS {
      ...,
      data-value-descriptor ABSENT
    })

    VIRAG-REAL ::= [UNIVERSAL 9] IMPLICIT SEQUENCE {
      mantissa INTEGER,
      base INTEGER (2|10),
      exponent INTEGER
    }

    VIRAG-TYPE-IDENTIFIER ::= CLASS
      {
        &id OBJECT IDENTIFIER UNIQUE,
        &Type
      }
      WITH SYNTAX {
        &Type IDENTIFIED BY &id
      }

    VIRAG-ABSTRACT-SYNTAX ::= CLASS {
      &id OBJECT IDENTIFIER UNIQUE,
      &Type,
      &property BIT STRING {handles-invalid-encodings(0)} DEFAULT {}
    }
    WITH SYNTAX {
      &Type IDENTIFIED BY &id [HAS PROPERTY &property]
    }

END
