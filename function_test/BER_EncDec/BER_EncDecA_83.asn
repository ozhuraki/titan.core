--/////////////////////////////////////////////////////////////////////////////
-- Copyright (c) 2000-2019 Ericsson Telecom AB
-- All rights reserved. This program and the accompanying materials
-- are made available under the terms of the Eclipse Public License v2.0
-- which accompanies this distribution, and is available at
-- https://www.eclipse.org/org/documents/epl-2.0/EPL-2.0.html
--
-- Contributors:
--   Kristof, Szabados
--
--/////////////////////////////////////////////////////////////////////////////
BER-EncDecA-83


DEFINITIONS ::=
BEGIN
BERPDU ::= CHOICE
      {
        a   NULL,
	b   BOOLEAN,
	c   INTEGER,
	d   ENUMERATED {first ,second ,third},
	e   REAL,
	f   BIT STRING,
	g   OCTET STRING,
	
	h   OBJECT IDENTIFIER,
	i   IA5String,
	j   CHOICE {x1 [1] BOOLEAN,
		    y1 [2] OCTET STRING},
	
	k   SEQUENCE{x2 NULL,
		     y2 BOOLEAN},
	
	l   SET { x3 BIT STRING,
		  y3 OCTET STRING},
		  
	m   [3] SEQUENCE OF INTEGER,
	n   [4] SET OF BOOLEAN	  
       }
       
       
        
END
